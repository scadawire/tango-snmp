PTP-8080-PTP-MIB DEFINITIONS ::= BEGIN
 
IMPORTS

     DisplayString, TEXTUAL-CONVENTION , DateAndTime,
     TruthValue
        FROM SNMPv2-TC

      Counter32, Gauge32, Integer32, Unsigned32, TimeTicks,
      OBJECT-TYPE, MODULE-IDENTITY , enterprises
                FROM SNMPv2-SMI

      MODULE-COMPLIANCE, OBJECT-GROUP
                FROM SNMPv2-CONF;                                                                           
                                         
ptpIdentity MODULE-IDENTITY
	LAST-UPDATED "201501231200Z"
	ORGANIZATION 
		"Brandywine Communications"
	CONTACT-INFO 
		"1153 Warner Ave
        Tustin, CA 92780
        U.S.A
        url: https://www.brandywinecomm.com           
        Phone +1 714 755 1050
        info@brandywinecomm.com"
	DESCRIPTION 
		"PTP-8080 private MIB"
		
	REVISION "201501231200Z"
	DESCRIPTION 
		"1.4 Property text change in for misc.ocDisable and MIB syntax fixes"

	REVISION "201409171200Z"
	DESCRIPTION 
		"1.3 productDescription, revisionData and userDescription changed from
		     Octet string to DisplayString character."

    REVISION "201401101200Z"
	DESCRIPTION 
		"1.2 Some MIB syntax errors fixes."

    REVISION "201311271200Z"
	DESCRIPTION 
		"1.1 Updated with ordinary clock disable function (TC functionality only).
         New read-only variable to get whether the clock is synchronized or not."

	REVISION "201310241200Z"
	DESCRIPTION 
		"1.0 First Revision."
         		         
::= { ptp 1 }

--  OIDs for PTP part of iNET MIB
--

  switches      OBJECT IDENTIFIER ::= { enterprises 34753 }
  ptp           OBJECT IDENTIFIER ::= { switches 1 }
  
  common		OBJECT IDENTIFIER ::= { ptp 2 }
  clockDesc		OBJECT IDENTIFIER ::= { ptp 3 }
  defaultds		OBJECT IDENTIFIER ::= { ptp 4 }
  currentds		OBJECT IDENTIFIER ::= { ptp 5 }
  parentds		OBJECT IDENTIFIER ::= { ptp 6 }
  timepropds	OBJECT IDENTIFIER ::= { ptp 7 }
  portds		OBJECT IDENTIFIER ::= { ptp 8 }
  tcdefaultds	OBJECT IDENTIFIER ::= { ptp 9 }
  tcportds		OBJECT IDENTIFIER ::= { ptp 10 }
  time			OBJECT IDENTIFIER ::= { ptp 11 }
  portSettings	OBJECT IDENTIFIER ::= { ptp 12 }
  misc      	OBJECT IDENTIFIER ::= { ptp 13 }
            
--
-- PTP clock description
-- IEEE 1588 Std 2008, chapter 15.5.3.1.2
--      

    mibVersion OBJECT-TYPE
	SYNTAX  DisplayString (SIZE(0..255))
        MAX-ACCESS read-only
        STATUS current
        DESCRIPTION
            "This parameter states the MIB revision supported on the target."
    ::= { common 1 }

    save OBJECT-TYPE
	SYNTAX  TruthValue
        MAX-ACCESS read-write
        STATUS current
        DESCRIPTION
            "Set this bit to True if you want to save the current parameters
            to flash. This bit will be reset to False after the parameters
            have been saved to flash."
    ::= { common 2 }    

    clockType OBJECT-TYPE
	SYNTAX DisplayString 
        MAX-ACCESS read-only
        STATUS current
        DESCRIPTION
            "The value clockType shall indicate the type of PTP node
            as defined in Table 42 of IEEE 1588 Std 2008.
            Bit 0 is the most significant bit (left-most bit) in the 
            bit field."
    ::= { clockDesc 1 }
                      
	physicalLayerProtocol OBJECT-TYPE                 
		SYNTAX DisplayString 
		MAX-ACCESS read-only 
		STATUS current 
		DESCRIPTION 
			"This parameter indicates the physical layer protocol, 
            e.g. Ethernet."
	::= { clockDesc 2 } 
        
	physicalAddressLength OBJECT-TYPE
		SYNTAX INTEGER (1..32) 
        MAX-ACCESS read-only
        STATUS current
        DESCRIPTION
            "This parameter specifies the length of the physical address."
    ::= { clockDesc 3 }
                      
    physicalAddress OBJECT-TYPE                 
		SYNTAX OCTET STRING (SIZE(2))
		MAX-ACCESS read-only 
		STATUS current 
		DESCRIPTION 
			"This parameter specifies the physical address, 
            e.g. MAC address." 
	::= { clockDesc 4 } 
                                                  
	protocolAddressNetworkProtocol OBJECT-TYPE
        SYNTAX  INTEGER {   
            reserved    (0),
            udpIPv4     (1),
            udpIPv6     (2),
            ieee802dot3 (3),
            deviceNet   (4),
            controlNet  (5),
            profinet    (6)
        }
        MAX-ACCESS read-write
        STATUS current
        DESCRIPTION
            "This parameter specifies the network protocol of the port address 
            indicated by the targetPortIdentity.portNumber."
    ::= { clockDesc 5 }
                                                  
	protocolAddressAddresslength OBJECT-TYPE
		SYNTAX INTEGER (1..65535) 
        MAX-ACCESS read-only
        STATUS current
        DESCRIPTION
            "This parameter specifies the length of the port address 
            indicated by the targetPortIdentity.portNumber."
    ::= { clockDesc 6 }
    
     protocolAddressAddressField OBJECT-TYPE                 
		SYNTAX OCTET STRING (SIZE(16)) 
		MAX-ACCESS read-only 
		STATUS current 
		DESCRIPTION 
			"This parameter specifies the port address indicated by 
			the targetPortIdentity.portNumber." 
	::= { clockDesc 7 } 
	
     manufacturerId OBJECT-TYPE                 
		SYNTAX OCTET STRING (SIZE(3)) 
		MAX-ACCESS read-only 
		STATUS current 
		DESCRIPTION 
			"This parameter indicates the manufacturer id." 
	::= { clockDesc 8 } 

     productDecription OBJECT-TYPE                 
		SYNTAX  DisplayString (SIZE(0..255))
		MAX-ACCESS read-only 
		STATUS current 
		DESCRIPTION 
			"This parameter specifies the manufactorer, 
			model number and instance identifer (MAC and/or serial no)." 
	::= { clockDesc 9 }  
	
     revisionData OBJECT-TYPE                 
		SYNTAX  DisplayString (SIZE(0..255))
		MAX-ACCESS read-only 
		STATUS current 
		DESCRIPTION 
			"This parameter specifies the HW, SW and/or FW version of the product." 
	::= { clockDesc 10 } 

     userDescription OBJECT-TYPE                 
		SYNTAX  DisplayString (SIZE(0..255))
		MAX-ACCESS read-write 
		STATUS current 
		DESCRIPTION 
			"This parameter specifies the user defined name of the device and user 
			defined physical location." 
	::= { clockDesc 11 }   	 	 

     profileIdentity OBJECT-TYPE                 
		SYNTAX OCTET STRING (SIZE(6)) 
		MAX-ACCESS read-only 
		STATUS current 
		DESCRIPTION 
			"This parameter specifies the PTP profile." 
	::= { clockDesc 12 }   	 
				
--
-- PTP set time
-- IEEE 1588 Std 2008, chapter 15.5.3.2.1
-- 
                
	currentTime OBJECT-TYPE
 		SYNTAX      DisplayString 
        MAX-ACCESS read-write
        STATUS current
        DESCRIPTION
            "This parameter specifies the PTP time.  The PTP clock can be set. 
            The syntax is 2011-01-02 01:23:45,000."
		::= { time 1 } 
		
--
-- PTP default data set 
-- IEEE 1588 Std 2008, chapter 15.5.3.3.1
-- 					
		
	defaultdsTwoStepFlag OBJECT-TYPE
		SYNTAX TruthValue
		MAX-ACCESS read-write 
		STATUS current 
		DESCRIPTION 
			"0x01 = Two step flag (*), 0x02 = Slave Only flag.
			(*) The IEEE1588 Std 2008 (v2) specifies that this flag shall be read-only, 
			but the user is allowed to modify this flag on this PTP clock implementation.
			The flag will be forced to 2-step operation if IEEE1588 Std 2002 (v1) is selected, 
			see portdsVersionNumber in the port data set." 
		::= { defaultds 1 }  			
		
	defaultdsNumberPorts OBJECT-TYPE
		SYNTAX INTEGER (1..65535) 
        MAX-ACCESS read-only
        STATUS current
        DESCRIPTION
            "This parameter specifies the number of ports on the clock."
		::= { defaultds 2 } 		

	defaultdsPriority1 OBJECT-TYPE
		SYNTAX INTEGER (0..255) 
		MAX-ACCESS read-write 
		STATUS current 
		DESCRIPTION 
			"This parameter is read from the defaultDS.priority1 member data set. Range:  [0 .. 255]" 
		::= { defaultds 3 } 

	defaultdsClockQualityClockClass OBJECT-TYPE
		SYNTAX INTEGER (0..255) 

		MAX-ACCESS read-only 
		STATUS current 
		DESCRIPTION 
			"This parameter is read from the defaultDS.clockQuality member data set. 
			See tabel 5 in IEEE 1588 Std 2008." 
		::= { defaultds 4 } 
                                        
	defaultdsClockQualityClockAccuracy OBJECT-TYPE
		SYNTAX OCTET STRING (SIZE(1)) 
		MAX-ACCESS read-only 
		STATUS current 
		DESCRIPTION 
			"This parameter is read from the defaultDS.clockQuality member data set.
			See tabel 5 in IEEE 1588 Std 2008." 
		::= { defaultds 5 }   
		
	defaultdsClockQualityOffsetScaledLogVariance OBJECT-TYPE
		SYNTAX INTEGER (1..65535) 
		MAX-ACCESS read-only 
		STATUS current 
		DESCRIPTION 
			"This parameter is read from the defaultDS.clockQuality member data set." 
		::= { defaultds 6 }  
		
	defaultdsPriority2 OBJECT-TYPE
		SYNTAX INTEGER (0..255) 
		MAX-ACCESS read-write 
		STATUS current 
		DESCRIPTION 
			"This parameter is read from the defaultDS.priority2 member data set. Range = [0 .. 255]." 
		::= { defaultds 7 } 

	defaultdsClockIdentity OBJECT-TYPE
		SYNTAX OCTET STRING (SIZE(8)) 
		MAX-ACCESS read-only 
		STATUS current 
		DESCRIPTION 
			"This parameter is read from the defaultDS.clockIdentity member data set." 
		::= { defaultds 8 } 

	defaultdsDomainNumber OBJECT-TYPE
		SYNTAX INTEGER (0..255) 
		MAX-ACCESS read-write 
		STATUS current 
		DESCRIPTION 
			"This parameter is read from the defaultDS.domainNumber member data set." 
		::= { defaultds 9 }
        
	slaveOnly OBJECT-TYPE
		SYNTAX TruthValue
		MAX-ACCESS read-write 
		STATUS current 
		DESCRIPTION 
			"True if slaveOnly mode, False otherwise." 
		::= { defaultds 10 } 
		

--
-- PTP current data set 
-- IEEE 1588 Std 2008, chapter 15.5.3.4.1
-- 	

	currentdsStepsRemoved OBJECT-TYPE
		SYNTAX INTEGER (1..65535) 
		MAX-ACCESS read-only 
		STATUS current 
		DESCRIPTION 
			"This parameter is read from the currentDS.stepsRemoved member data set." 
		::= { currentds 1 }  

	currentdsOffsetFromMasterScaledNanoseconds2 OBJECT-TYPE
		SYNTAX INTEGER
		MAX-ACCESS read-only 
		STATUS current 
		DESCRIPTION 
			"This parameter is read from the currentDS.OffsetFromMaster member data set." 
		::= { currentds 2 }  		

	currentdsOffsetFromMasterScaledNanoseconds OBJECT-TYPE
		SYNTAX Unsigned32
		MAX-ACCESS read-only 
		STATUS current 
		DESCRIPTION 
			"This parameter is read from the currentDS.OffsetFromMaster member data set." 
		::= { currentds 3 }  		
				                                     
	currentdsMeanPathDelayScaledNanoseconds2 OBJECT-TYPE
		SYNTAX INTEGER
		MAX-ACCESS read-only 
		STATUS current 
		DESCRIPTION 
			"This parameter is read from the currentDS.meanPathDelay member data set." 
		::= { currentds 4 }

	currentdsMeanPathDelayScaledNanoseconds OBJECT-TYPE
		SYNTAX Unsigned32
		MAX-ACCESS read-only 
		STATUS current 
		DESCRIPTION 
			"This parameter is read from the currentDS.meanPathDelay member data set." 
		::= { currentds 5 }
				                


--
-- PTP parent data set 
-- IEEE 1588 Std 2008, chapter 15.5.3.4.1
-- 	
				                
	parentdsPortIdentityClockId OBJECT-TYPE
		SYNTAX OCTET STRING (SIZE(8)) 
		MAX-ACCESS read-only 
		STATUS current 
		DESCRIPTION 
			"This parameter is read from the parentDS.parentPortIdentity member data set." 
		::= { parentds 1 } 

	parentdsPortIdentityPortNumber OBJECT-TYPE
		SYNTAX INTEGER (1..65535) 
		MAX-ACCESS read-only 
		STATUS current 
		DESCRIPTION 
			"This parameter is read from the parentDS.parentPortIdentity member data set." 
		::= { parentds 2 } 

	parentdsParentStats OBJECT-TYPE
		SYNTAX  INTEGER {   
            false (0),   -- False
            true (1)   	-- True
        }
		MAX-ACCESS read-only 
		STATUS current 
		DESCRIPTION 
			"This parameter is read from the parentDS.parentStats member data set.
			The value of parentDS.parentStats shall indicate whether the values of
			parentDS.observedParentOffsetScaledLogVariance and parentDS.observedParentClockPhaseChangeRate
			have been measured and are valid. A TRUE value shall indicate valid data."	
		::= { parentds 3 } 	
		
	parentdsObservedParentOffsetScaledLogVariance OBJECT-TYPE
		SYNTAX INTEGER (1..65535) 
		MAX-ACCESS read-only 
		STATUS current 
		DESCRIPTION 
			"This parameter is read from the parentDS.observedParentOffsetScaledLogVariance member data set."	
		::= { parentds 4 } 	
		
	parentdsObservedParentClockPhaseChangeRate OBJECT-TYPE
		SYNTAX INTEGER  
		MAX-ACCESS read-only 
		STATUS current 
		DESCRIPTION 
			"This parameter is read from the parentDS.observedParentClockPhaseChangeRate member data set."	
		::= { parentds 5 } 	
		                      
	parentdsGrandmasterPriority1 OBJECT-TYPE
		SYNTAX INTEGER (0..255) 
		MAX-ACCESS read-only 
		STATUS current 
		DESCRIPTION 
			"This parameter is read from the parentDS.grandmasterPriority1 member data set."	
		::= { parentds 6 } 			                      
		                      		
	parentdsGrandmasterClockQualityClockClass OBJECT-TYPE
		SYNTAX INTEGER (0..255) 
		MAX-ACCESS read-only 
		STATUS current 
		DESCRIPTION 
			"This parameter is read from the parentDS.grandmasterClockQuality member data set."	
		::= { parentds 7 }
		 	
	parentdsGrandmasterClockQualityClockAccuracy OBJECT-TYPE
		SYNTAX OCTET STRING (SIZE(1)) 
		MAX-ACCESS read-only 
		STATUS current 
		DESCRIPTION 
			"This parameter is read from the parentDS.grandmasterClockQuality member data set."	
		::= { parentds 8 } 	                                
		
	parentdsGrandmasterClockQualityOffsetScaledLogVariance OBJECT-TYPE
		SYNTAX INTEGER (1..65535) 
		MAX-ACCESS read-only 
		STATUS current 
		DESCRIPTION 
			"This parameter is read from the parentDS.grandmasterClockQuality member data set."	
		::= { parentds 9 } 
		
	parentdsGrandmasterPriority2 OBJECT-TYPE
		SYNTAX INTEGER (0..255) 
		MAX-ACCESS read-only 
		STATUS current 
		DESCRIPTION 
			"This parameter is read from the parentDS.grandmasterPriority2 member data set."	
		::= { parentds 10 }		
		
	parentdsGrandmasterIdentity OBJECT-TYPE
		SYNTAX OCTET STRING (SIZE(8)) 
		MAX-ACCESS read-only 
		STATUS current 
		DESCRIPTION 
			"This parameter is read from the parentDS.grandmasterIdentity member data set."	
		::= { parentds 11 } 	  		
               
               
--
-- PTP time property data set 
-- IEEE 1588 Std 2008, chapter 15.5.3.6.1
--                

	timepropdsCurrentUTCOffset OBJECT-TYPE
		SYNTAX INTEGER (-32768..32767) 
		MAX-ACCESS read-only 
		STATUS current 
		DESCRIPTION 
			"This parameter is read from the timePropertiesDS.currentUtcOffset member data set."	
		::= { timepropds 1 } 

	timepropdsCurrentUTCOffsetValid OBJECT-TYPE
		SYNTAX TruthValue
		MAX-ACCESS read-only 
		STATUS current 
		DESCRIPTION 
			"This parameter is read from the timePropertiesDS.currentUtcOffsetValid member data set."	
		::= { timepropds 2 } 

	timepropdsLeap59 OBJECT-TYPE
		SYNTAX TruthValue
		MAX-ACCESS read-only 
		STATUS current 
		DESCRIPTION 
			"This parameter is read from the timePropertiesDS.leap59 member data set."	
		::= { timepropds 3 }  

	timepropdsLeap61 OBJECT-TYPE
		SYNTAX TruthValue
		MAX-ACCESS read-only 
		STATUS current 
		DESCRIPTION 
			"This parameter is read from the timePropertiesDS.leap61 member data set."	
		::= { timepropds 4 }

	timepropdsTimeTraceable OBJECT-TYPE
		SYNTAX TruthValue
		MAX-ACCESS read-only 
		STATUS current 
		DESCRIPTION 
			"This parameter is read from the timePropertiesDS.timeTraceable member data set."	
		::= { timepropds 5 }   

	timepropdsFrequencyTraceable OBJECT-TYPE
		SYNTAX TruthValue
		MAX-ACCESS read-only 
		STATUS current 
		DESCRIPTION 
			"This parameter is read from the timePropertiesDS.frequencyTraceable member data set."	
		::= { timepropds 6 }  

	timepropdsPTPTimescale OBJECT-TYPE
		SYNTAX TruthValue
		MAX-ACCESS read-only 
		STATUS current 
		DESCRIPTION 
			"This parameter is read from the timePropertiesDS.ptpTimescale member data set."	
		::= { timepropds 7 }           

	timepropdsTimeSource OBJECT-TYPE
		SYNTAX OCTET STRING (SIZE(1))  
		MAX-ACCESS read-only 
		STATUS current 
		DESCRIPTION 
			"This parameter is read from the timePropertiesDS.timeSource member data set."	
		::= { timepropds 8 } 	
         
         
--
-- PTP port data set 
-- IEEE 1588 Std 2008, chapter 15.5.3.7.1
--                   
		
	portdsTable OBJECT-TYPE 
		SYNTAX SEQUENCE OF PortdsEntry 
		MAX-ACCESS not-accessible 
		STATUS current 
		DESCRIPTION 
			"Table of PTP port data set parameters" 
	::= { portds 1 } 
			
	portdsEntry OBJECT-TYPE 
		SYNTAX PortdsEntry 
		MAX-ACCESS not-accessible 
		STATUS current 
		DESCRIPTION 
			"Entry in the PTP port data set." 
		INDEX { portdsIndex } 
	::= { portdsTable 1 } 
	
	PortdsEntry ::= SEQUENCE { 
		portdsIndex 
		Unsigned32, 
		portdsPortIdentityClockId 
		OCTET STRING, 
		portdsPortIdentityPortNumber 
		INTEGER, 
		portdsPortState 
		INTEGER, 
		portdsLogMinDelayReqInterval 
		INTEGER, 
		portdsPeerMeanPathDelayScaledNanoseconds2 
		INTEGER,
		portdsPeerMeanPathDelayScaledNanoseconds
		Unsigned32,   
		portdsLogAnnounceInterval
		INTEGER,
		portdsAnnounceReceiptTimeout
		INTEGER,
		portdsLogSyncInterval
		INTEGER,
		portdsDelayMechanism						 
		INTEGER,
		portdsLogMinPdelayReqInterval				
		INTEGER,
		portdsVersionNumber				
		INTEGER
	}  
	portdsIndex OBJECT-TYPE 
		SYNTAX Unsigned32 
		MAX-ACCESS not-accessible 
		STATUS current 
		DESCRIPTION 
		"Index for the portds Table." 
		DEFVAL { 1 } 
		::= { portdsEntry 1 } 
	                 	                   
	portdsPortIdentityClockId OBJECT-TYPE
		SYNTAX OCTET STRING (SIZE(8))  
		MAX-ACCESS read-only 
		STATUS current 
		DESCRIPTION 
			"This parameter is read from the portDS.portIdentity member data set."	
		::= { portdsEntry 2 } 	

	portdsPortIdentityPortNumber OBJECT-TYPE
		SYNTAX INTEGER (1..65535) 
		MAX-ACCESS read-only 
		STATUS current 
		DESCRIPTION 
			"This parameter is read from the portDS.portIdentity member data set."	
		::= { portdsEntry 3 } 	

	portdsPortState OBJECT-TYPE
		SYNTAX  INTEGER {   
            initializing (1),   
            faulty (2),
            disabled (3),    
            listening (4),
			premaster (5),
			master (6),
			passive (7),
			uncalibrated (8),
			slave (9)
        }
  
		MAX-ACCESS read-only 
		STATUS current 
		DESCRIPTION 
			"This parameter is read from the portDS.portStats member data set.
			See table 8 in IEEE1588 Std 2008."	
		::= { portdsEntry 4 } 	

	portdsLogMinDelayReqInterval OBJECT-TYPE
		SYNTAX INTEGER  
		MAX-ACCESS read-only 
		STATUS current 
		DESCRIPTION 
			"This parameter is read from the portDS.logMinDelayReqInterval member data set."	
		::= { portdsEntry 5 } 	

	portdsPeerMeanPathDelayScaledNanoseconds2 OBJECT-TYPE
		SYNTAX INTEGER
		MAX-ACCESS read-only 
		STATUS current 
		DESCRIPTION 
			"This parameter is read from the portDS.peerMeanPathDelay member data set."	
		::= { portdsEntry 6 } 	

	portdsPeerMeanPathDelayScaledNanoseconds OBJECT-TYPE
		SYNTAX Unsigned32  
		MAX-ACCESS read-only 
		STATUS current 
		DESCRIPTION 
			"This parameter is read from the portDS.peerMeanPathDelay member data set."	
		::= { portdsEntry 7 } 	

	portdsLogAnnounceInterval OBJECT-TYPE
		SYNTAX INTEGER  
		MAX-ACCESS read-write 
		STATUS current 
		DESCRIPTION 
			"This parameter is read from the portDS.logAnnounceInterval member data set."	
		::= { portdsEntry 8 } 	

	portdsAnnounceReceiptTimeout OBJECT-TYPE
		SYNTAX INTEGER  
		MAX-ACCESS read-write 
		STATUS current 
		DESCRIPTION 
			"This parameter is read from the portDS.announceReceiptTimeout member data set."	
		::= { portdsEntry 9 } 	

	portdsLogSyncInterval OBJECT-TYPE
		SYNTAX INTEGER  
		MAX-ACCESS read-write 
		STATUS current 
		DESCRIPTION 
			"This parameter is read from the portDS.logSyncInterval member data set."	
		::= { portdsEntry 10 } 	

	portdsDelayMechanism OBJECT-TYPE
		SYNTAX  INTEGER {   
            e2e (1),   
            p2p (2)
        }

		MAX-ACCESS read-write 
		STATUS current 
		DESCRIPTION 
			"This parameter is read from the portDS.delayMechanism member data set."	
		::= { portdsEntry 11 }

	portdsLogMinPdelayReqInterval OBJECT-TYPE
		SYNTAX INTEGER 
		MAX-ACCESS read-write 
		STATUS current 
		DESCRIPTION 
			"This parameter is read from the portDS.logMinPdelayReqInterval member data set."	
		::= { portdsEntry 12 } 	

	portdsVersionNumber OBJECT-TYPE
	SYNTAX  INTEGER {   
            ptpv1 (1),   
            ptpv2 (2)
        }
		MAX-ACCESS read-write 
		STATUS current 
		DESCRIPTION 
			"This parameter is read from the portDS.versionNumber member data set."	
		::= { portdsEntry 13 }

       
--
-- PTP TC default data set 
-- IEEE 1588 Std 2008, chapter 15.5.3.7.1
--           
	tcdefaultdsClockId OBJECT-TYPE
		SYNTAX OCTET STRING (SIZE(8))  
		MAX-ACCESS read-only 
		STATUS current 
		DESCRIPTION 
			"This parameter is read from the transparentClockPortDS.portIdentity.clockIdentity member data 
			set and is common for all ports."	
		::= { tcdefaultds 1 } 	

	tcdefaultdsNumberPorts OBJECT-TYPE
		SYNTAX INTEGER (1..65535) 
		MAX-ACCESS read-only 
		STATUS current 
		DESCRIPTION 
			"This parameter is read from the transparentClockPortDS.portIdentity.numberPorts member data 
			set for each of the ports on the TC switch."	
		::= { tcdefaultds 2 } 	

	tcdefaultdsDelayMechanism OBJECT-TYPE
		SYNTAX  INTEGER {   
            e2e (1),   
            p2p (2)
        }
		MAX-ACCESS read-only 
		STATUS current 
		DESCRIPTION 
			"This parameter is read from the defaultDS.delayMechanism member data set 
			(same as for port data set)."	
		::= { tcdefaultds 3 } 	

	tcdefaultdsPrimaryDomain OBJECT-TYPE
		SYNTAX INTEGER (0..255) 
		MAX-ACCESS read-only 
		STATUS current 
		DESCRIPTION 
			"This parameter is read from the of the primaryDomain member of the 
			transparentClockDefaultDS data set"	
		::= { tcdefaultds 4 } 	

--  
-- PTP TC Port data set 
-- IEEE 1588 Std 2008, chapter 
--       

	tcportdsTable OBJECT-TYPE 
		SYNTAX SEQUENCE OF TcportdsEntry 
		MAX-ACCESS not-accessible 
		STATUS current 
		DESCRIPTION 
			"Table of PTP TC port data set parameters" 
	::= { tcportds 1 } 
			
	tcportdsEntry OBJECT-TYPE 
		SYNTAX TcportdsEntry 
		MAX-ACCESS not-accessible 
		STATUS current 
		DESCRIPTION 
			"Entry in the PTP TC port data set." 
		INDEX { tcportdsIndex } 
	::= { tcportdsTable 1 } 
	
	TcportdsEntry ::= SEQUENCE { 
		tcportdsIndex 
		Unsigned32, 
		tcportdsPortIdClockId 
		OCTET STRING,
		tcportdsPortIdPortNumber
		Unsigned32,
		tcportdsFaultyFlag
		OCTET STRING,
		tcportdsLogMinPdelayReqInterval
		Unsigned32,
		tcportdsPeerMeanPathDelayScaledNanoseconds2
		INTEGER,
        tcportdsPeerMeanPathDelayScaledNanoseconds
		Unsigned32		
	}
	  
	tcportdsIndex OBJECT-TYPE 
		SYNTAX Unsigned32 
		MAX-ACCESS not-accessible 
		STATUS current 
		DESCRIPTION 
		"Index for the tcportds Table." 
		DEFVAL { 1 } 
		::= { tcportdsEntry 1 } 
		
	tcportdsPortIdClockId OBJECT-TYPE
		SYNTAX OCTET STRING (SIZE(8))  
		MAX-ACCESS read-only 
		STATUS current 
		DESCRIPTION 
			"This parameter is read from the transparentClockPortDS.portIdentity member data set."	
		::= { tcportdsEntry 2 } 	

	tcportdsPortIdPortNumber OBJECT-TYPE
		SYNTAX Unsigned32 
		MAX-ACCESS read-only 
		STATUS current 
		DESCRIPTION 
			"This parameter is read from the transparentClockPortDS.portIdentity.numberPorts member data 
			set for each of the ports on the TC switch."	
		::= { tcportdsEntry 3 } 	        
		
	tcportdsFaultyFlag OBJECT-TYPE
		SYNTAX OCTET STRING (SIZE(1)) 
		MAX-ACCESS read-only 
		STATUS current 
		DESCRIPTION
			"This parameter is read from the transparentClockPortDS.faultyFlag member data set for each port."			
		::= { tcportdsEntry 4 } 	

	tcportdsLogMinPdelayReqInterval OBJECT-TYPE
		SYNTAX Unsigned32  
		MAX-ACCESS read-only 
		STATUS current 
		DESCRIPTION
			"This parameter is read from the transparentClockPortDS.logMinPdelayReqInterval member data set
			and is common for all ports."	
		::= { tcportdsEntry 5 }

	tcportdsPeerMeanPathDelayScaledNanoseconds2 OBJECT-TYPE
		SYNTAX INTEGER 
		MAX-ACCESS read-only 
		STATUS current 
		DESCRIPTION
			"This parameter is read from the transparentClockPortDS.peerMeanPathDelay member data set for each port."			
		::= { tcportdsEntry 6 }

	tcportdsPeerMeanPathDelayScaledNanoseconds OBJECT-TYPE
		SYNTAX Unsigned32 		  
		MAX-ACCESS read-only 
		STATUS current 
		DESCRIPTION
			"This parameter is read from the transparentClockPortDS.peerMeanPathDelay member data set. for each port."			
		::= { tcportdsEntry 7 }

	
--  
-- PTP per port settings
--

    perPortEnabled OBJECT-TYPE
	SYNTAX TruthValue
        MAX-ACCESS read-write
        STATUS current
        DESCRIPTION
            "This parameter enabled/disables the per-port PTP settings."
    ::= { portSettings 1 } 

	portSettingsTable OBJECT-TYPE 
		SYNTAX SEQUENCE OF PortSettingsEntry 
		MAX-ACCESS not-accessible 
		STATUS current 
		DESCRIPTION 
			"PTP per port settings" 
	::= { portSettings 2 } 
			
	portSettingsEntry OBJECT-TYPE 
		SYNTAX PortSettingsEntry 
		MAX-ACCESS not-accessible 
		STATUS current 
		DESCRIPTION 
			"Entry in the PTP TC port data set." 
		INDEX { portSettingsIndex } 
	::= { portSettingsTable 1 } 
	
	PortSettingsEntry ::= SEQUENCE { 
		portSettingsIndex 
		Unsigned32, 
		ptpEnabled 
		INTEGER,
		ptpVersion
		INTEGER,
		networkProtocol
		INTEGER,
		delayMechanism
		INTEGER		
	}
	  
	portSettingsIndex OBJECT-TYPE 
		SYNTAX Unsigned32 
		MAX-ACCESS not-accessible 
		STATUS current 
		DESCRIPTION 
		"Index for the table." 
		DEFVAL { 1 } 
		::= { portSettingsEntry 1 } 
		
	ptpEnabled OBJECT-TYPE
		SYNTAX TruthValue
		MAX-ACCESS read-write 
		STATUS current 
		DESCRIPTION 
			"PTP can be enabled per port. True if enabled. False if disabled."	
		::= { portSettingsEntry 2 } 	

	ptpVersion OBJECT-TYPE
		SYNTAX  INTEGER {   
            v1 (1),   
            v2 (2)
        }
		MAX-ACCESS read-write 
		STATUS current 
		DESCRIPTION 
			"This parameter is read from the transparentClockPortDS.portIdentity.numberPorts member data 
			set for each of the ports on the TC switch."	
		::= { portSettingsEntry 3 } 	        
		
	networkProtocol OBJECT-TYPE
		SYNTAX  INTEGER {   
            udpIPv4 (1),   
            ieee802dot1 (3)
        }
		MAX-ACCESS read-write 
		STATUS current 
		DESCRIPTION
			"This parameter is read from the transparentClockPortDS.faultyFlag member data set for each port."			
		::= { portSettingsEntry 4 } 	

	delayMechanism OBJECT-TYPE
		SYNTAX  INTEGER {   
            e2e (1),   
            p2p (2)         
        }
		MAX-ACCESS read-write 
		STATUS current 
		DESCRIPTION
			"This parameter is read from the transparentClockPortDS.logMinPdelayReqInterval member data set
			and is common for all ports."	
		::= { portSettingsEntry 5 }
        
--  
-- misc
--   
        
    sysUTCOffset OBJECT-TYPE
	SYNTAX INTEGER
        MAX-ACCESS read-write
        STATUS current
        DESCRIPTION
            "This parameter sets the system UTC offset which is the offset
            between the current time scale and the UTC timescale. This will
            only have effect on the PTP master and will be ignored when
            an external time source like GPS is used."
    ::= { misc 1 }

   mlogDelayReqInterval OBJECT-TYPE
	SYNTAX  INTEGER (-5..7)
		MAX-ACCESS read-write 
		STATUS current 
		DESCRIPTION 
			"This parameter is the log2(interval) where interval is the number
            of seconds between the delay requests coming from the slave clock.
            
            Note that the minimum value of this interval is given by the PTP
            protocol and can be found in the portdsLogMinDelayReqInterval
            parameter. It can also not be more than logSyncInterval of the
            master clock plus five."	
		::= { misc 2 }
        
    mlogMessageIntervalDelayResp OBJECT-TYPE
	SYNTAX  INTEGER (-5..7)
		MAX-ACCESS read-write 
		STATUS current 
		DESCRIPTION 
			"This parameter is the logMessageInterval described in the 
            IEEE1588 2008 standard that is sent in the delay response 
            messages from the master. 
            
            Note that the PTP protocol put some restrictions on the values
            of this parameters. It can minimum be the value of logSyncInterval
            and maximum the value of logSyncInterval+5."
		::= { misc 3 }

    ocDisable OBJECT-TYPE
	SYNTAX  TruthValue
		MAX-ACCESS read-write 
		STATUS current 
		DESCRIPTION 
			"When set to true the ordinary clock is disabled.
             When the ordinary clock is disabled the switch will only function
             as a transparent clock with no master functionality.
             
             When set to False the ordinary clock is enabled."
		::= { misc 4 }

    synchronized OBJECT-TYPE
	SYNTAX  TruthValue
		MAX-ACCESS read-only 
		STATUS current 
		DESCRIPTION 
			"When set to true the clock is synchronized either to an external timebase
            like GPS or another master in the network. If the clock is the master but
            with free running clock, this variable will always return True.
             
             When set to False the clock is not synchronized."
		::= { misc 5 }         
 
END
