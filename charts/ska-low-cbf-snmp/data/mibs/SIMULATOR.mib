SIMULATOR-MIB DEFINITIONS ::= BEGIN

IMPORTS
    MODULE-IDENTITY, OBJECT-TYPE, Integer32,
    NOTIFICATION-TYPE, enterprises                       FROM SNMPv2-SMI
    OBJECT-GROUP    FROM SNMPv2-CONF
;


simulator MODULE-IDENTITY
    LAST-UPDATED "201312190000Z"
    ORGANIZATION "www.example.com"
    CONTACT-INFO    
	 "postal:   John Doe
                    123 Main Street
                    Anytown, CA 00000

          email:    xyz-mib@example.com"
    DESCRIPTION
	"First draft"
    ::= { enterprises 1 }  
    
    
    netSnmpExampleScalars       OBJECT IDENTIFIER ::= { simulator 1 }
    groups  OBJECT IDENTIFIER ::= { simulator 2 }
    
    netSnmpExampleInteger OBJECT-TYPE
    SYNTAX      Integer32
    MAX-ACCESS  read-write
    STATUS      current
    DESCRIPTION
	"This is a simple object which merely houses a writable
	 integer.  It's only purposes is to hold the value of a single
	 integer.  Writing to it will simply change the value for
	 subsequent GET/GETNEXT/GETBULK retrievals.

	 This example object is implemented in the
	 agent/mibgroup/examples/scalar_int.c file."
    DEFVAL { 42 }
    ::= { netSnmpExampleScalars 1 }
   
   
   myGroup
    OBJECT-GROUP
    OBJECTS {
         netSnmpExampleInteger
         }
    STATUS  current
    DESCRIPTION
        "a group"
    ::= { groups 1 }
    
END
