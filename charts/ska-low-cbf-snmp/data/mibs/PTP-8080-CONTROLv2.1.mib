PTP-8080-CONTROL-MIB DEFINITIONS ::= BEGIN

IMPORTS

    DisplayString, TEXTUAL-CONVENTION , DateAndTime,
    TruthValue, RowStatus
        FROM SNMPv2-TC
    Counter32, Gauge32, Integer32, Unsigned32, TimeTicks,
    OBJECT-TYPE, MODULE-IDENTITY , enterprises, IpAddress
        FROM SNMPv2-SMI
    MODULE-COMPLIANCE, OBJECT-GROUP
        FROM SNMPv2-CONF;                                                                           
                                         
controlIdentity MODULE-IDENTITY
	LAST-UPDATED "201503121200Z"
	ORGANIZATION 
		"Brandywine Communications"
	CONTACT-INFO 
		"1153 Warner Ave
        Tustin, CA 92780
        U.S.A
        url: https://www.brandywinecomm.com           
        Phone +1 714 755 1050
        info@brandywinecomm.com"
	DESCRIPTION 
		"PTP-8080 private MIB"

    REVISION "201503121200Z"
	DESCRIPTION 
		"2.1 Syntax fixes.
		     ntpClientEnable is removed. externalTimeBase is used instead."

	REVISION "201406271200Z"
	DESCRIPTION 
		"2.0 Added index filtering and NTP client parameters."

	REVISION "201311271200Z"
	DESCRIPTION 
		"1.1 Some read-only variables are made read-write.
         Added more descriptions for some of the variables."

	REVISION "201310241200Z"
	DESCRIPTION 
		"1.0 First Revision."

         
        
::= { control 1 }

switches            OBJECT IDENTIFIER ::= { enterprises 34753 }
brandywine          OBJECT IDENTIFIER ::= { switches 0 }
ptp8080             OBJECT IDENTIFIER ::= { brandywine 10 }
control             OBJECT IDENTIFIER ::= { ptp8080 84 }

serialPorts         OBJECT IDENTIFIER ::= { control 2 }
gps                 OBJECT IDENTIFIER ::= { control 3 }
gpsEmulation        OBJECT IDENTIFIER ::= { control 4 }
udpFilter           OBJECT IDENTIFIER ::= { control 5 }
gpio                OBJECT IDENTIFIER ::= { control 6 }
saveConfiguration   OBJECT IDENTIFIER ::= { control 7 }
features            OBJECT IDENTIFIER ::= { control 8 }
status              OBJECT IDENTIFIER ::= { control 9 }
indexFilter         OBJECT IDENTIFIER ::= { control 10 }
ntp                 OBJECT IDENTIFIER ::= { control 11 }


    rs232Port1Function OBJECT-TYPE
	SYNTAX  INTEGER {   
            console (1),   
            gps-emulation (2),
            external-gps (3)
        }
        MAX-ACCESS read-write
        STATUS current
        DESCRIPTION
            "The PTP CPU's console port can be used for more than console port.
            If the switch is setup to emulate GPS, the NMEA report will be sent
            out on this port. Also, if an external GPS receiver is used, 
            this RS232 port can be used to get the NMEA input signals.
            
            Note that the PTP CPU has to have a console port defined. 
            If this port is not used as a console port, then
            rs422Port1Function must be configured as console port.
            
            A reboot of the switch is required before this setting will work."
    ::= { serialPorts 1 }
    
    rs232Port1Baudrate OBJECT-TYPE
	SYNTAX  INTEGER {   
            b9600 (1),
            b19200 (2),
            b38400 (3),
            b57600 (4),
            b115200 (5)
        }
        MAX-ACCESS read-write
        STATUS current
        DESCRIPTION
            "This is the baudrate of the RS232 port for the PTP CPU."
    ::= { serialPorts 2 }
    
    rs422Port1Function OBJECT-TYPE
	SYNTAX  INTEGER {   
            console (1),
            gpio1(4)
        }
        MAX-ACCESS read-write
        STATUS current
        DESCRIPTION
            "console: The RS422 port can be used as an optional console port for the PTP
            CPU if the regular RS232 port has a different configuration.
            
            gpio1: The RS422 port can output a digital signal that is setup for
            GPO1 in the gpio OID. This can be a PPS signal, IRIG-B signal etc."
    ::= { serialPorts 3 }
    
    rs422Port1Baudrate OBJECT-TYPE
	SYNTAX  INTEGER {               
            b9600 (1),
            b19200 (2),
            b38400 (3),
            b57600 (4),
            b115200 (5)
        }
        MAX-ACCESS read-write
        STATUS current
        DESCRIPTION
            "This is the baudrate of the RS422 port if it is used as a console
            port. Note that if the port function is 'gpio1', then the baudrate 
            has no meaning."
    ::= { serialPorts 4 }
    
    rs422Port2Function OBJECT-TYPE
	SYNTAX  INTEGER {   
            gpio2 (4)
        }
        MAX-ACCESS read-write
        STATUS current
        DESCRIPTION
            "gpio2: The RS422 port can output a digital signal that is setup for
            GPO2 in the gpio OID. This can be a PPS signal, IRIG-B signal etc."
    ::= { serialPorts 5 }
    
    rs422Port2Baudrate OBJECT-TYPE
	SYNTAX  INTEGER {   
            b9600 (1),
            b19200 (2),
            b38400 (3),
            b57600 (4),
            b115200 (5)
        }
        MAX-ACCESS read-write
        STATUS current
        DESCRIPTION
            "The baudrate currently has no meaning."
    ::= { serialPorts 6 }
    
--
-- GPS    
--
    externalTimeBase OBJECT-TYPE
	SYNTAX  INTEGER {
            off(0),
            built-in-gps(1),
            external-gps(2),
			ntp-client(3),
			irigb-002(4)
        }
        MAX-ACCESS read-write
        STATUS current
        DESCRIPTION
            "Off means no external time base is used. Internal oscillator will be used.
            
            Built-in GPS means that the built-in GPS will be used. An external antenna must be connected.
            
            External-gps means an external GPS unit is used. The NMEA report must
            be input on the RS232 channel on the PTP CPU.
			
			If an NTP server is available then the NTP client can be enabled on the switch. The switch
			will then synchronize its clock to the NTP server clock.
			
			The switch can synchronize its clock to an IRIGB-002 input if that is available. If the
			hardware supports general purpose input signals or RS422, then those can be used.
            
            Note: It will only be possible to enable the GPS if this feature is available and the
			PTP slaveOnly flag is not set."
    ::= { gps 1 }
    
    gpsLock OBJECT-TYPE
	SYNTAX  TruthValue
        MAX-ACCESS read-only
        STATUS current
        DESCRIPTION
            "True if the GPS is locked to a satellite, False otherwise."
    ::= { gps 2 }
    
    synchronized OBJECT-TYPE
	SYNTAX  TruthValue
        MAX-ACCESS read-only
        STATUS current
        DESCRIPTION
            "True if the switch is synchronized to an external timebase, False otherwise."
    ::= { gps 3 }
    
    cableDelay OBJECT-TYPE
	SYNTAX  Unsigned32
        MAX-ACCESS read-write
        STATUS current
        DESCRIPTION
            "If you have a very long GPS cable, it will introduce some
            time delay. This parameter can be used to compensate for that. 
            The cableDelay is specified as the length of the GPS cable
            in meters."
    ::= { gps 4 }
    
--
-- GPS emulation    
--
    gpsEmulationEnabled OBJECT-TYPE
	SYNTAX  TruthValue
        MAX-ACCESS read-only
        STATUS current
        DESCRIPTION
            "True if the GPS emulation is enabled, False otherwise.
            It will be enabled if the rs232 port of the PTP CPU is
            setup to emulate GPS and the emulation feature is enabled."
    ::= { gpsEmulation 1 }
    
    nmeaDelay OBJECT-TYPE
	SYNTAX  INTEGER (200..800)
        MAX-ACCESS read-write
        STATUS current
        DESCRIPTION
            "Delay in ms after the PPS goes high until the NMEA report is
            sent out."
    ::= { gpsEmulation 2 }

    gprmcReportEnabled OBJECT-TYPE
	SYNTAX  TruthValue
        MAX-ACCESS read-write
        STATUS current
        DESCRIPTION
            "True if the GPS emulation sends out the GPRMC report, 
            False otherwise."
    ::= { gpsEmulation 3 }
    
    pOTNStatusReportEnabled OBJECT-TYPE
	SYNTAX  TruthValue
        MAX-ACCESS read-write
        STATUS current
        DESCRIPTION
            "True if the GPS emulation sends out the Brandywine proprietary 
            NMEA telegram for PTP status, False otherwise.
            The telegram looks like this:
                $POTNSTAT,status,,,,,,,*crc\r\n
            where status is a hexadecimal byte b6b5b4b3b2b1b0 where 
                b0=master receives GPS signal
                b1=master is in sync with input signal
                b2=master receives PPS signal
                b3=master receives necessary NMEA strings
                b4=spare bit
                b5=unit is a slave to a master
                b6=slave in in sync with a master
                b7=spare bit"
    ::= { gpsEmulation 4 }
    
--  
-- UDP port filters for switch port 1
--
	udpPortFilterPort1Table OBJECT-TYPE 
		SYNTAX SEQUENCE OF UDPPortFilterPort1Entry 
		MAX-ACCESS not-accessible 
		STATUS current 
		DESCRIPTION 
			"UDP filters for switch port 1.
            
            Note: This will only work if the UDP filtering feature is enabled."
	::= { udpFilter 1 }
			
	udpPortFilterPort1Entry OBJECT-TYPE 
		SYNTAX UDPPortFilterPort1Entry 
		MAX-ACCESS not-accessible 
		STATUS current 
		DESCRIPTION 
			"Entry in the UDP port filter table." 
		INDEX { udpPortFilterPort1Index } 
	::= { udpPortFilterPort1Table 1 } 
	
	UDPPortFilterPort1Entry ::= SEQUENCE { 
		udpPortFilterPort1Index 
		Unsigned32, 
		p1UdpPort 
		INTEGER,
		p1Status
		RowStatus		
	}
	  
	udpPortFilterPort1Index OBJECT-TYPE 
		SYNTAX Unsigned32 
		MAX-ACCESS not-accessible 
		STATUS current 
		DESCRIPTION 
		"Index for the table." 
		DEFVAL { 1 } 
		::= { udpPortFilterPort1Entry 1 }
        
    p1UdpPort OBJECT-TYPE 
		SYNTAX INTEGER (1..65535)
		MAX-ACCESS read-write
		STATUS current 
		DESCRIPTION 
		"UDP port number." 
		DEFVAL { 1 } 
		::= { udpPortFilterPort1Entry 2 }
        
    p1Status OBJECT-TYPE 
		SYNTAX RowStatus
		MAX-ACCESS read-create
		STATUS current 
		DESCRIPTION 
		"Only createAndGo(4) is allowed when creating a new filter." 
		DEFVAL { 4 } 
		::= { udpPortFilterPort1Entry 3 }
        
--  
-- UDP port filters for switch port 2
--
  	udpPortFilterPort2Table OBJECT-TYPE 
		SYNTAX SEQUENCE OF UDPPortFilterPort2Entry 
		MAX-ACCESS not-accessible 
		STATUS current 
		DESCRIPTION 
			"UDP filters for switch port 2.
            
            Note: This will only work if the UDP filtering feature is enabled." 
	::= { udpFilter 2 }   
			
	udpPortFilterPort2Entry OBJECT-TYPE 
		SYNTAX UDPPortFilterPort2Entry 
		MAX-ACCESS not-accessible 
		STATUS current 
		DESCRIPTION 
			"Entry in the UDP port filter table." 
		INDEX { udpPortFilterPort2Index } 
	::= { udpPortFilterPort2Table 1 } 
	
	UDPPortFilterPort2Entry ::= SEQUENCE { 
		udpPortFilterPort2Index 
		Unsigned32, 
		p2UdpPort 
		INTEGER,
		p2Status
		RowStatus		
	}  
        
    udpPortFilterPort2Index OBJECT-TYPE 
		SYNTAX Unsigned32 
		MAX-ACCESS not-accessible 
		STATUS current 
		DESCRIPTION 
		"Index for the table." 
		DEFVAL { 1 } 
		::= { udpPortFilterPort2Entry 1 }
        
    p2UdpPort OBJECT-TYPE 
		SYNTAX INTEGER (1..65535)
		MAX-ACCESS read-write
		STATUS current 
		DESCRIPTION 
		"UDP port number." 
		DEFVAL { 1 } 
		::= { udpPortFilterPort2Entry 2 }
        
    p2Status OBJECT-TYPE 
		SYNTAX RowStatus
		MAX-ACCESS read-create
		STATUS current 
		DESCRIPTION 
		"." 
		DEFVAL { 1 } 
		::= { udpPortFilterPort2Entry 3 }
      
--  
-- UDP port filters for switch port 3
--
  	udpPortFilterPort3Table OBJECT-TYPE 
		SYNTAX SEQUENCE OF UDPPortFilterPort3Entry 
		MAX-ACCESS not-accessible 
		STATUS current 
		DESCRIPTION 
			"UDP filters for switch port 3.
            
            Note: This will only work if the UDP filtering feature is enabled." 
	::= { udpFilter 3 }   
			
	udpPortFilterPort3Entry OBJECT-TYPE 
		SYNTAX UDPPortFilterPort3Entry 
		MAX-ACCESS not-accessible 
		STATUS current 
		DESCRIPTION 
			"Entry in the UDP port filter table." 
		INDEX { udpPortFilterPort3Index } 
	::= { udpPortFilterPort3Table 1 } 
	
	UDPPortFilterPort3Entry ::= SEQUENCE { 
		udpPortFilterPort3Index 
		Unsigned32, 
		p3UdpPort 
		INTEGER,
		p3Status
		RowStatus		
	}  
        
    udpPortFilterPort3Index OBJECT-TYPE 
		SYNTAX Unsigned32 
		MAX-ACCESS not-accessible 
		STATUS current 
		DESCRIPTION 
		"Index for the table." 
		DEFVAL { 1 } 
		::= { udpPortFilterPort3Entry 1 }
        
    p3UdpPort OBJECT-TYPE 
		SYNTAX INTEGER (1..65535)
		MAX-ACCESS read-write
		STATUS current 
		DESCRIPTION 
		"UDP port number." 
		DEFVAL { 1 } 
		::= { udpPortFilterPort3Entry 2 }
        
    p3Status OBJECT-TYPE 
		SYNTAX RowStatus
		MAX-ACCESS read-create
		STATUS current 
		DESCRIPTION 
		"." 
		DEFVAL { 1 } 
		::= { udpPortFilterPort3Entry 3 }

--  
-- UDP port filters for switch port 4
--
  	udpPortFilterPort4Table OBJECT-TYPE 
		SYNTAX SEQUENCE OF UDPPortFilterPort4Entry 
		MAX-ACCESS not-accessible 
		STATUS current 
		DESCRIPTION 
			"UDP filters for switch port 4.
            
            Note: This will only work if the UDP filtering feature is enabled." 
	::= { udpFilter 4 }   
			
	udpPortFilterPort4Entry OBJECT-TYPE 
		SYNTAX UDPPortFilterPort4Entry 
		MAX-ACCESS not-accessible 
		STATUS current 
		DESCRIPTION 
			"Entry in the UDP port filter table." 
		INDEX { udpPortFilterPort4Index } 
	::= { udpPortFilterPort4Table 1 } 
	
	UDPPortFilterPort4Entry ::= SEQUENCE { 
		udpPortFilterPort4Index 
		Unsigned32, 
		p4UdpPort 
		INTEGER,
		p4Status
		RowStatus		
	}  
        
    udpPortFilterPort4Index OBJECT-TYPE 
		SYNTAX Unsigned32 
		MAX-ACCESS not-accessible 
		STATUS current 
		DESCRIPTION 
		"Index for the table." 
		DEFVAL { 1 } 
		::= { udpPortFilterPort4Entry 1 }
        
    p4UdpPort OBJECT-TYPE 
		SYNTAX INTEGER (1..65535)
		MAX-ACCESS read-write
		STATUS current 
		DESCRIPTION 
		"UDP port number." 
		DEFVAL { 1 } 
		::= { udpPortFilterPort4Entry 2 }
        
    p4Status OBJECT-TYPE 
		SYNTAX RowStatus
		MAX-ACCESS read-create
		STATUS current 
		DESCRIPTION 
		"." 
		DEFVAL { 1 } 
		::= { udpPortFilterPort4Entry 3 }

--  
-- UDP port filters for switch port 5
--
  	udpPortFilterPort5Table OBJECT-TYPE 
		SYNTAX SEQUENCE OF UDPPortFilterPort5Entry 
		MAX-ACCESS not-accessible 
		STATUS current 
		DESCRIPTION 
			"UDP filters for switch port 5.
            
            Note: This will only work if the UDP filtering feature is enabled." 
	::= { udpFilter 5 }   
			
	udpPortFilterPort5Entry OBJECT-TYPE 
		SYNTAX UDPPortFilterPort5Entry 
		MAX-ACCESS not-accessible 
		STATUS current 
		DESCRIPTION 
			"Entry in the UDP port filter table." 
		INDEX { udpPortFilterPort5Index } 
	::= { udpPortFilterPort5Table 1 } 
	
	UDPPortFilterPort5Entry ::= SEQUENCE { 
		udpPortFilterPort5Index 
		Unsigned32, 
		p5UdpPort 
		INTEGER,
		p5Status
		RowStatus		
	}  
        
    udpPortFilterPort5Index OBJECT-TYPE 
		SYNTAX Unsigned32 
		MAX-ACCESS not-accessible 
		STATUS current 
		DESCRIPTION 
		"Index for the table." 
		DEFVAL { 1 } 
		::= { udpPortFilterPort5Entry 1 }
        
    p5UdpPort OBJECT-TYPE 
		SYNTAX INTEGER (1..65535)
		MAX-ACCESS read-write
		STATUS current 
		DESCRIPTION 
		"UDP port number." 
		DEFVAL { 1 } 
		::= { udpPortFilterPort5Entry 2 }
        
    p5Status OBJECT-TYPE 
		SYNTAX RowStatus
		MAX-ACCESS read-create
		STATUS current 
		DESCRIPTION 
		"." 
		DEFVAL { 1 } 
		::= { udpPortFilterPort5Entry 3 }

--  
-- UDP port filters for switch port 6
--
  	udpPortFilterPort6Table OBJECT-TYPE 
		SYNTAX SEQUENCE OF UDPPortFilterPort6Entry 
		MAX-ACCESS not-accessible 
		STATUS current 
		DESCRIPTION 
			"UDP filters for switch port 6.
            
            Note: This will only work if the UDP filtering feature is enabled." 
	::= { udpFilter 6 }   
			
	udpPortFilterPort6Entry OBJECT-TYPE 
		SYNTAX UDPPortFilterPort6Entry 
		MAX-ACCESS not-accessible 
		STATUS current 
		DESCRIPTION 
			"Entry in the UDP port filter table." 
		INDEX { udpPortFilterPort6Index } 
	::= { udpPortFilterPort6Table 1 } 
	
	UDPPortFilterPort6Entry ::= SEQUENCE { 
		udpPortFilterPort6Index 
		Unsigned32, 
		p6UdpPort 
		INTEGER,
		p6Status
		RowStatus		
	}  
        
    udpPortFilterPort6Index OBJECT-TYPE 
		SYNTAX Unsigned32 
		MAX-ACCESS not-accessible 
		STATUS current 
		DESCRIPTION 
		"Index for the table." 
		DEFVAL { 1 } 
		::= { udpPortFilterPort6Entry 1 }
        
    p6UdpPort OBJECT-TYPE 
		SYNTAX INTEGER (1..65535)
		MAX-ACCESS read-write
		STATUS current 
		DESCRIPTION 
		"UDP port number." 
		DEFVAL { 1 } 
		::= { udpPortFilterPort6Entry 2 }
        
    p6Status OBJECT-TYPE 
		SYNTAX RowStatus
		MAX-ACCESS read-create
		STATUS current 
		DESCRIPTION 
		"." 
		DEFVAL { 1 } 
		::= { udpPortFilterPort6Entry 3 }

--  
-- UDP port filters for switch port 7
--
  	udpPortFilterPort7Table OBJECT-TYPE 
		SYNTAX SEQUENCE OF UDPPortFilterPort7Entry 
		MAX-ACCESS not-accessible 
		STATUS current 
		DESCRIPTION 
			"UDP filters for switch port 7.
            
            Note: This will only work if the UDP filtering feature is enabled." 
	::= { udpFilter 7 }   
			
	udpPortFilterPort7Entry OBJECT-TYPE 
		SYNTAX UDPPortFilterPort7Entry 
		MAX-ACCESS not-accessible 
		STATUS current 
		DESCRIPTION 
			"Entry in the UDP port filter table." 
		INDEX { udpPortFilterPort7Index } 
	::= { udpPortFilterPort7Table 1 } 
	
	UDPPortFilterPort7Entry ::= SEQUENCE { 
		udpPortFilterPort7Index 
		Unsigned32, 
		p7UdpPort 
		INTEGER,
		p7Status
		RowStatus		
	}  
        
    udpPortFilterPort7Index OBJECT-TYPE 
		SYNTAX Unsigned32 
		MAX-ACCESS not-accessible 
		STATUS current 
		DESCRIPTION 
		"Index for the table." 
		DEFVAL { 1 } 
		::= { udpPortFilterPort7Entry 1 }
        
    p7UdpPort OBJECT-TYPE 
		SYNTAX INTEGER (1..65535)
		MAX-ACCESS read-write
		STATUS current 
		DESCRIPTION 
		"UDP port number." 
		DEFVAL { 1 } 
		::= { udpPortFilterPort7Entry 2 }
        
    p7Status OBJECT-TYPE 
		SYNTAX RowStatus
		MAX-ACCESS read-create
		STATUS current 
		DESCRIPTION 
		"." 
		DEFVAL { 1 } 
		::= { udpPortFilterPort7Entry 3 }

--  
-- UDP port filters for switch port 8
--
  	udpPortFilterPort8Table OBJECT-TYPE 
		SYNTAX SEQUENCE OF UDPPortFilterPort8Entry 
		MAX-ACCESS not-accessible 
		STATUS current 
		DESCRIPTION 
			"UDP filters for switch port 8.
            
            Note: This will only work if the UDP filtering feature is enabled." 
	::= { udpFilter 8 }   
			
	udpPortFilterPort8Entry OBJECT-TYPE 
		SYNTAX UDPPortFilterPort8Entry 
		MAX-ACCESS not-accessible 
		STATUS current 
		DESCRIPTION 
			"Entry in the UDP port filter table." 
		INDEX { udpPortFilterPort8Index } 
	::= { udpPortFilterPort8Table 1 } 
	
	UDPPortFilterPort8Entry ::= SEQUENCE { 
		udpPortFilterPort8Index 
		Unsigned32, 
		p8UdpPort 
		INTEGER,
		p8Status
		RowStatus		
	}  
        
    udpPortFilterPort8Index OBJECT-TYPE 
		SYNTAX Unsigned32 
		MAX-ACCESS not-accessible 
		STATUS current 
		DESCRIPTION 
		"Index for the table." 
		DEFVAL { 1 } 
		::= { udpPortFilterPort8Entry 1 }
        
    p8UdpPort OBJECT-TYPE 
		SYNTAX INTEGER (1..65535)
		MAX-ACCESS read-write
		STATUS current 
		DESCRIPTION 
		"UDP port number." 
		DEFVAL { 1 } 
		::= { udpPortFilterPort8Entry 2 }
        
    p8Status OBJECT-TYPE 
		SYNTAX RowStatus
		MAX-ACCESS read-create
		STATUS current 
		DESCRIPTION 
		"." 
		DEFVAL { 1 } 
		::= { udpPortFilterPort8Entry 3 }
        
--  
-- UDP filter configuration
--

	udpFilterConfigTable OBJECT-TYPE 
		SYNTAX SEQUENCE OF UDPFilterConfigEntry 
		MAX-ACCESS not-accessible 
		STATUS current 
		DESCRIPTION 
			"This table configures the UDP filters.
            
            Note: This will only work if the UDP filtering feature is enabled." 
	::= { udpFilter 9 } 
			
	udpFilterConfigEntry OBJECT-TYPE 
		SYNTAX UDPFilterConfigEntry 
		MAX-ACCESS not-accessible 
		STATUS current 
		DESCRIPTION 
			"" 
		INDEX { udpFilterIndex } 
	::= { udpFilterConfigTable 1 } 
	
	UDPFilterConfigEntry ::= SEQUENCE { 
		udpFilterIndex 
		Unsigned32, 
		udpFilterMode 
		INTEGER,
		udpFilterField
		INTEGER,
		udpFilterDestPort
		INTEGER,
        udpFilterEnable
        INTEGER
	}
	  
	udpFilterIndex OBJECT-TYPE 
		SYNTAX Unsigned32 
		MAX-ACCESS not-accessible 
		STATUS current 
		DESCRIPTION 
		"Index for the table." 
		DEFVAL { 1 } 
		::= { udpFilterConfigEntry 1 }
		
	udpFilterMode OBJECT-TYPE
		SYNTAX  INTEGER {   
            block (0),
            allow (1)
        }
		MAX-ACCESS read-write 
		STATUS current 
		DESCRIPTION 
			"Block means all UDP packets with a source/destination port number 
            matching the UDP port filter will be blocked. 
            All other packets will be allowed.
            
            Allow means all UDP packets with a source/destination port number
            matching the UDP port filter will be allowed. 
            All other packets will be blocked.
            
            Whether to filter on the UDP source port, the UDP destination port
            or both is specified in the udpFilterField."
		::= { udpFilterConfigEntry 2 } 	

	udpFilterField OBJECT-TYPE
		SYNTAX  INTEGER {   
            udpSrcPort (0),
            udpDestPort (1),
            udpSrcAndDestPort (2)
        }
		MAX-ACCESS read-write 
		STATUS current 
		DESCRIPTION 
			"udpSrcPort: The UDP source port in the packet will be 
            matched against the UDP filters.
            
            udpDestPort: The UDP destination port in the packet will be 
            matched against the UDP filters.
            
            udpSrcAndDestPort: The UDP source port in the packet will be 
            matched against the UDP filters and the destination port in
            the packet will be matched against the destination port
            specified in the udpFilterDestPort OID."
		::= { udpFilterConfigEntry 3 } 	        
		
	udpFilterDestPort OBJECT-TYPE
		SYNTAX  INTEGER (1..65535)
		MAX-ACCESS read-write 
		STATUS current 
		DESCRIPTION
			"If udpFilterField is set to udpSrcAndDestPort, the destination
            port is specified in this entry."	
		::= { udpFilterConfigEntry 4 }
        
    udpFilterEnable OBJECT-TYPE
        SYNTAX  TruthValue
        MAX-ACCESS read-write 
        STATUS current 
        DESCRIPTION
            "True if the UDP filter is enabled, False otherwise."	
        ::= { udpFilterConfigEntry 5 }
        
        
        
        
--  
-- GPIO setup
--

	gpioTable OBJECT-TYPE 
		SYNTAX SEQUENCE OF GPIOEntry 
		MAX-ACCESS not-accessible 
		STATUS current 
		DESCRIPTION 
			"This table configures the general purpose out signals.
            
            Index 1-8 describe the general purpose output (GPO) signals GPO1-GPO8.
            Index 9 describes the standard PPS output signal referred to as OUT1 in
            the connector pinout description.
            
            Note that GPO1 and GPO2 can be output on the RS422 interfaces as well
            if those interfaces are set up for that (see OID serialPorts).
            
            Note: It will only be possible to configure I/O if this feature is available."
	::= { gpio 1 } 
			
	gpioEntry OBJECT-TYPE 
		SYNTAX GPIOEntry 
		MAX-ACCESS not-accessible 
		STATUS current 
		DESCRIPTION 
			"" 
		INDEX { gpioIndex } 
	::= { gpioTable 1 } 
	
	GPIOEntry ::= SEQUENCE { 
		gpioIndex 
		Unsigned32,
        output
        INTEGER,
		signal 
		INTEGER,
        enabled
        TruthValue
	}

	gpioIndex OBJECT-TYPE 
		SYNTAX Unsigned32 
		MAX-ACCESS not-accessible 
		STATUS current 
		DESCRIPTION 
		"Index for the table." 
		DEFVAL { 1 } 
		::= { gpioEntry 1 }
        
   	output OBJECT-TYPE
		SYNTAX  INTEGER {   
            gpo1 (0),
            gpo2 (1),
            gpo3 (2),
            gpo4 (3),
            gpo5 (4),
            gpo6 (5),
            gpo7 (6),
            gpo8 (7),
            pps (8)
        }
		MAX-ACCESS read-only 
		STATUS current 
		DESCRIPTION 
			"The output signal pin where the signal will be applied."
		::= { gpioEntry 2 }
		
	signal OBJECT-TYPE
		SYNTAX  INTEGER {   
            pps (0),
            irigb-002 (1),
            clk100Hz (2)
        }
		MAX-ACCESS read-write 
		STATUS current 
		DESCRIPTION 
			"pps: The pulse per second (PPS) signal is output on the GPO pin.
            irigb-002: IRIG-B002 (DC) is output on the GPO pin.
            clk100Hz: A 100 Hz signal is output on the GPO pin."
		::= { gpioEntry 3 }
        
    enabled OBJECT-TYPE
	SYNTAX  TruthValue
        MAX-ACCESS read-write
        STATUS current
        DESCRIPTION
            "True if the GPO signal is enabled, False otherwise."
    ::= { gpioEntry 4 }

--  
-- saveConfiguration
-- 
    
    save OBJECT-TYPE
	SYNTAX  TruthValue
        MAX-ACCESS read-write
        STATUS current
        DESCRIPTION
            "Set this bit to True if you want to save the current parameters
            to flash. This bit will be reset to False after the parameters
            have been saved to flash."
    ::= { saveConfiguration 1 }
    
    
--  
-- features
-- 
    
    ptpV1 OBJECT-TYPE
	SYNTAX  TruthValue
        MAX-ACCESS read-only
        STATUS current
        DESCRIPTION
            "True if the PTPv1 feature is enabled, false otherwise."
    ::= { features 1 }  

    ptpV2 OBJECT-TYPE
	SYNTAX  TruthValue
        MAX-ACCESS read-only
        STATUS current
        DESCRIPTION
            "True if PTPv2 feature is enabled, false otherwise."
    ::= { features 2 }  

    gpsCapable OBJECT-TYPE
	SYNTAX  TruthValue
        MAX-ACCESS read-only
        STATUS current
        DESCRIPTION
            "True if the switch is capable of using a GPS as external timebase, false otherwise."
    ::= { features 3 }  

    masterCapable OBJECT-TYPE
	SYNTAX  TruthValue
        MAX-ACCESS read-only
        STATUS current
        DESCRIPTION
            "True if the switch can become PTP master, false otherwise."
    ::= { features 4 }
    
    ntpServer OBJECT-TYPE
	SYNTAX  TruthValue
        MAX-ACCESS read-only
        STATUS current
        DESCRIPTION
            "True if the NTP server feature is enabled, false otherwise."
    ::= { features 5 } 
    
    gpsEmulationCapable OBJECT-TYPE
	SYNTAX  TruthValue
        MAX-ACCESS read-only
        STATUS current
        DESCRIPTION
            "True if the GPS emulation feature is enabled, false otherwise."
    ::= { features 6 }
    
    irigB-002 OBJECT-TYPE
	SYNTAX  TruthValue
        MAX-ACCESS read-only
        STATUS current
        DESCRIPTION
            "True if the IRIG-B (DC) feature is enabled, false otherwise."
    ::= { features 7 } 
    
    irigB-122 OBJECT-TYPE
	SYNTAX  TruthValue
        MAX-ACCESS read-only
        STATUS current
        DESCRIPTION
            "True if the IRIG-B (AM) feature is enabled, false otherwise."
    ::= { features 8 }

    oneStep OBJECT-TYPE
	SYNTAX  TruthValue
        MAX-ACCESS read-only
        STATUS current
        DESCRIPTION
            "True if the PTPv2 one-step feature is enabled, false otherwise."
    ::= { features 9 }  
    
    twoStep OBJECT-TYPE
	SYNTAX  TruthValue
        MAX-ACCESS read-only
        STATUS current
        DESCRIPTION
            "True if the PTP two-step feature is enabled, false otherwise."
    ::= { features 10 }
    
    slaveCapable OBJECT-TYPE
	SYNTAX  TruthValue
        MAX-ACCESS read-only
        STATUS current
        DESCRIPTION
            "True if the PTP slave feature is enabled, false otherwise."
    ::= { features 11 } 
    
    udpFiltering OBJECT-TYPE
	SYNTAX  TruthValue
        MAX-ACCESS read-only
        STATUS current
        DESCRIPTION
            "True if the UDP filtering feature is enabled, false otherwise."
    ::= { features 12 }  
    
    v1v2Translator OBJECT-TYPE
	SYNTAX  TruthValue
        MAX-ACCESS read-only
        STATUS current
        DESCRIPTION
            "True if PTP version 1 <-> PTP version 2 feature is enabled, false otherwise."
    ::= { features 13 }
    
    gpioFeature OBJECT-TYPE
	SYNTAX  TruthValue
        MAX-ACCESS read-only
        STATUS current
        DESCRIPTION
            "True if the GPIO feature is enabled, false otherwise."
    ::= { features 14 }
    
productVersion OBJECT-TYPE
    SYNTAX  DisplayString (SIZE (0..255))
    MAX-ACCESS read-only
    STATUS current
    DESCRIPTION
        "Description of the switch software/firmware revision."
    ::= { status 1 }













































--  
-- Index filters for switch port 1
--
	indexFilterPort1Table OBJECT-TYPE 
		SYNTAX SEQUENCE OF IndexFilterPort1Entry 
		MAX-ACCESS not-accessible 
		STATUS current 
		DESCRIPTION 
			"Index filters for switch port 1.
            
            Note: This will only work if the index filtering feature is enabled."
	::= { indexFilter 1 }
			
	indexFilterPort1Entry OBJECT-TYPE 
		SYNTAX IndexFilterPort1Entry 
		MAX-ACCESS not-accessible 
		STATUS current 
		DESCRIPTION 
			"Entry in the index port filter table." 
		INDEX { indexFilterPort1Index } 
	::= { indexFilterPort1Table 1 } 
	
	IndexFilterPort1Entry ::= SEQUENCE { 
		indexFilterPort1Index 
		Unsigned32, 
		filterPort1 
		Unsigned32,
        validEgressPort1
        TruthValue,
		validIngressPort1
        TruthValue,
		filterStatusPort1
		RowStatus		
	}
	  
	indexFilterPort1Index OBJECT-TYPE 
		SYNTAX Unsigned32 
		MAX-ACCESS not-accessible 
		STATUS current 
		DESCRIPTION 
		"Index for the table." 
		DEFVAL { 1 } 
		::= { indexFilterPort1Entry 1 }
        
    filterPort1 OBJECT-TYPE 
		SYNTAX Unsigned32
		MAX-ACCESS read-write
		STATUS current 
		DESCRIPTION 
		"A maximum 4 byte filter that shall be matched.
         Less than 4 bytes can be matched if the mask is set up for that." 
		DEFVAL { 1 } 
		::= { indexFilterPort1Entry 2 }
        
    validEgressPort1 OBJECT-TYPE 
		SYNTAX  TruthValue
		MAX-ACCESS read-write
		STATUS current 
		DESCRIPTION 
		"True if this filter is valid on egress." 
		DEFVAL { 2 } 
		::= { indexFilterPort1Entry 3 }

    validIngressPort1 OBJECT-TYPE 
		SYNTAX  TruthValue
		MAX-ACCESS read-write
		STATUS current 
		DESCRIPTION 
		"True if this filter is valid on ingress." 
		DEFVAL { 2 } 
		::= { indexFilterPort1Entry 4 }
        
    filterStatusPort1 OBJECT-TYPE 
		SYNTAX RowStatus
		MAX-ACCESS read-create
		STATUS current 
		DESCRIPTION 
		"Only createAndGo(4) is allowed when creating a new filter." 
		DEFVAL { 4 } 
		::= { indexFilterPort1Entry 5 }

    
--  
-- Index filters for switch port 2
--
	indexFilterPort2Table OBJECT-TYPE 
		SYNTAX SEQUENCE OF IndexFilterPort2Entry 
		MAX-ACCESS not-accessible 
		STATUS current 
		DESCRIPTION 
			"Index filters for switch port 2.
            
            Note: This will only work if the index filtering feature is enabled."
	::= { indexFilter 2 }
			
	indexFilterPort2Entry OBJECT-TYPE 
		SYNTAX IndexFilterPort2Entry 
		MAX-ACCESS not-accessible 
		STATUS current 
		DESCRIPTION 
			"Entry in the index port filter table." 
		INDEX { indexFilterPort2Index } 
	::= { indexFilterPort2Table 1 } 
	
	IndexFilterPort2Entry ::= SEQUENCE { 
		indexFilterPort2Index 
		Unsigned32, 
		filterPort2 
		Unsigned32,
        validEgressPort2
        TruthValue,
		validIngressPort2
        TruthValue,
		filterStatusPort2
		RowStatus		
	}
	  
	indexFilterPort2Index OBJECT-TYPE 
		SYNTAX Unsigned32 
		MAX-ACCESS not-accessible 
		STATUS current 
		DESCRIPTION 
		"Index for the table." 
		DEFVAL { 1 } 
		::= { indexFilterPort2Entry 1 }
        
    filterPort2 OBJECT-TYPE 
		SYNTAX Unsigned32
		MAX-ACCESS read-write
		STATUS current 
		DESCRIPTION 
		"A maximum 4 byte filter that shall be matched.
         Less than 4 bytes can be matched if the mask is set up for that." 
		DEFVAL { 1 } 
		::= { indexFilterPort2Entry 2 }
        
    validEgressPort2 OBJECT-TYPE 
		SYNTAX  TruthValue
		MAX-ACCESS read-write
		STATUS current 
		DESCRIPTION 
		"True if this filter is valid on egress." 
		DEFVAL { 2 } 
		::= { indexFilterPort2Entry 3 }

    validIngressPort2 OBJECT-TYPE 
		SYNTAX  TruthValue
		MAX-ACCESS read-write
		STATUS current 
		DESCRIPTION 
		"True if this filter is valid on ingress." 
		DEFVAL { 2 } 
		::= { indexFilterPort2Entry 4 }
        
    filterStatusPort2 OBJECT-TYPE 
		SYNTAX RowStatus
		MAX-ACCESS read-create
		STATUS current 
		DESCRIPTION 
		"Only createAndGo(4) is allowed when creating a new filter." 
		DEFVAL { 4 } 
		::= { indexFilterPort2Entry 5 }    
    
--  
-- Index filters for switch port 3
--
	indexFilterPort3Table OBJECT-TYPE 
		SYNTAX SEQUENCE OF IndexFilterPort3Entry 
		MAX-ACCESS not-accessible 
		STATUS current 
		DESCRIPTION 
			"Index filters for switch port 3.
            
            Note: This will only work if the index filtering feature is enabled."
	::= { indexFilter 3 }
			
	indexFilterPort3Entry OBJECT-TYPE 
		SYNTAX IndexFilterPort3Entry 
		MAX-ACCESS not-accessible 
		STATUS current 
		DESCRIPTION 
			"Entry in the index port filter table." 
		INDEX { indexFilterPort3Index } 
	::= { indexFilterPort3Table 1 } 
	
	IndexFilterPort3Entry ::= SEQUENCE { 
		indexFilterPort3Index 
		Unsigned32, 
		filterPort3 
		Unsigned32,
        validEgressPort3
        TruthValue,
		validIngressPort3
        TruthValue,
		filterStatusPort3
		RowStatus		
	}
	  
	indexFilterPort3Index OBJECT-TYPE 
		SYNTAX Unsigned32 
		MAX-ACCESS not-accessible 
		STATUS current 
		DESCRIPTION 
		"Index for the table." 
		DEFVAL { 1 } 
		::= { indexFilterPort3Entry 1 }
        
    filterPort3 OBJECT-TYPE 
		SYNTAX Unsigned32
		MAX-ACCESS read-write
		STATUS current 
		DESCRIPTION 
		"A maximum 4 byte filter that shall be matched.
         Less than 4 bytes can be matched if the mask is set up for that." 
		DEFVAL { 1 } 
		::= { indexFilterPort3Entry 2 }
        
    validEgressPort3 OBJECT-TYPE 
		SYNTAX  TruthValue
		MAX-ACCESS read-write
		STATUS current 
		DESCRIPTION 
		"True if this filter is valid on egress." 
		DEFVAL { 2 } 
		::= { indexFilterPort3Entry 3 }

    validIngressPort3 OBJECT-TYPE 
		SYNTAX  TruthValue
		MAX-ACCESS read-write
		STATUS current 
		DESCRIPTION 
		"True if this filter is valid on ingress." 
		DEFVAL { 2 } 
		::= { indexFilterPort3Entry 4 }
        
    filterStatusPort3 OBJECT-TYPE 
		SYNTAX RowStatus
		MAX-ACCESS read-create
		STATUS current 
		DESCRIPTION 
		"Only createAndGo(4) is allowed when creating a new filter." 
		DEFVAL { 4 } 
		::= { indexFilterPort3Entry 5 }        
    
--  
-- Index filters for switch port 4
--
	indexFilterPort4Table OBJECT-TYPE 
		SYNTAX SEQUENCE OF IndexFilterPort4Entry 
		MAX-ACCESS not-accessible 
		STATUS current 
		DESCRIPTION 
			"Index filters for switch port 4.
            
            Note: This will only work if the index filtering feature is enabled."
	::= { indexFilter 4 }
			
	indexFilterPort4Entry OBJECT-TYPE 
		SYNTAX IndexFilterPort4Entry 
		MAX-ACCESS not-accessible 
		STATUS current 
		DESCRIPTION 
			"Entry in the index port filter table." 
		INDEX { indexFilterPort4Index } 
	::= { indexFilterPort4Table 1 } 
	
	IndexFilterPort4Entry ::= SEQUENCE { 
		indexFilterPort4Index 
		Unsigned32, 
		filterPort4 
		Unsigned32,
        validEgressPort4
        TruthValue,
		validIngressPort4
        TruthValue,
		filterStatusPort4
		RowStatus		
	}
	  
	indexFilterPort4Index OBJECT-TYPE 
		SYNTAX Unsigned32 
		MAX-ACCESS not-accessible 
		STATUS current 
		DESCRIPTION 
		"Index for the table." 
		DEFVAL { 1 } 
		::= { indexFilterPort4Entry 1 }
        
    filterPort4 OBJECT-TYPE 
		SYNTAX Unsigned32
		MAX-ACCESS read-write
		STATUS current 
		DESCRIPTION 
		"A maximum 4 byte filter that shall be matched.
         Less than 4 bytes can be matched if the mask is set up for that." 
		DEFVAL { 1 } 
		::= { indexFilterPort4Entry 2 }
        
    validEgressPort4 OBJECT-TYPE 
		SYNTAX  TruthValue
		MAX-ACCESS read-write
		STATUS current 
		DESCRIPTION 
		"True if this filter is valid on egress." 
		DEFVAL { 2 } 
		::= { indexFilterPort4Entry 3 }

    validIngressPort4 OBJECT-TYPE 
		SYNTAX  TruthValue
		MAX-ACCESS read-write
		STATUS current 
		DESCRIPTION 
		"True if this filter is valid on ingress." 
		DEFVAL { 2 } 
		::= { indexFilterPort4Entry 4 }
        
    filterStatusPort4 OBJECT-TYPE 
		SYNTAX RowStatus
		MAX-ACCESS read-create
		STATUS current 
		DESCRIPTION 
		"Only createAndGo(4) is allowed when creating a new filter." 
		DEFVAL { 4 } 
		::= { indexFilterPort4Entry 5 }  
    
--  
-- Index filters for switch port 5
--
	indexFilterPort5Table OBJECT-TYPE 
		SYNTAX SEQUENCE OF IndexFilterPort5Entry 
		MAX-ACCESS not-accessible 
		STATUS current 
		DESCRIPTION 
			"Index filters for switch port 5.
            
            Note: This will only work if the index filtering feature is enabled."
	::= { indexFilter 5 }
			
	indexFilterPort5Entry OBJECT-TYPE 
		SYNTAX IndexFilterPort5Entry 
		MAX-ACCESS not-accessible 
		STATUS current 
		DESCRIPTION 
			"Entry in the index port filter table." 
		INDEX { indexFilterPort5Index } 
	::= { indexFilterPort5Table 1 } 
	
	IndexFilterPort5Entry ::= SEQUENCE { 
		indexFilterPort5Index 
		Unsigned32, 
		filterPort5 
		Unsigned32,
        validEgressPort5
        TruthValue,
		validIngressPort5
        TruthValue,
		filterStatusPort5
		RowStatus		
	}
	  
	indexFilterPort5Index OBJECT-TYPE 
		SYNTAX Unsigned32 
		MAX-ACCESS not-accessible 
		STATUS current 
		DESCRIPTION 
		"Index for the table." 
		DEFVAL { 1 } 
		::= { indexFilterPort5Entry 1 }
        
    filterPort5 OBJECT-TYPE 
		SYNTAX Unsigned32
		MAX-ACCESS read-write
		STATUS current 
		DESCRIPTION 
		"A maximum 4 byte filter that shall be matched.
         Less than 4 bytes can be matched if the mask is set up for that." 
		DEFVAL { 1 } 
		::= { indexFilterPort5Entry 2 }
        
    validEgressPort5 OBJECT-TYPE 
		SYNTAX  TruthValue
		MAX-ACCESS read-write
		STATUS current 
		DESCRIPTION 
		"True if this filter is valid on egress." 
		DEFVAL { 2 } 
		::= { indexFilterPort5Entry 3 }

    validIngressPort5 OBJECT-TYPE 
		SYNTAX  TruthValue
		MAX-ACCESS read-write
		STATUS current 
		DESCRIPTION 
		"True if this filter is valid on ingress." 
		DEFVAL { 2 } 
		::= { indexFilterPort5Entry 4 }
        
    filterStatusPort5 OBJECT-TYPE 
		SYNTAX RowStatus
		MAX-ACCESS read-create
		STATUS current 
		DESCRIPTION 
		"Only createAndGo(4) is allowed when creating a new filter." 
		DEFVAL { 4 } 
		::= { indexFilterPort5Entry 5 }    

--  
-- Index filters for switch port 6
--
	indexFilterPort6Table OBJECT-TYPE 
		SYNTAX SEQUENCE OF IndexFilterPort6Entry 
		MAX-ACCESS not-accessible 
		STATUS current 
		DESCRIPTION 
			"Index filters for switch port 6.
            
            Note: This will only work if the index filtering feature is enabled."
	::= { indexFilter 6 }
			
	indexFilterPort6Entry OBJECT-TYPE 
		SYNTAX IndexFilterPort6Entry 
		MAX-ACCESS not-accessible 
		STATUS current 
		DESCRIPTION 
			"Entry in the index port filter table." 
		INDEX { indexFilterPort6Index } 
	::= { indexFilterPort6Table 1 } 
	
	IndexFilterPort6Entry ::= SEQUENCE { 
		indexFilterPort6Index 
		Unsigned32, 
		filterPort6 
		Unsigned32,
        validEgressPort6
        TruthValue,
		validIngressPort6
        TruthValue,
		filterStatusPort6
		RowStatus		
	}
	  
	indexFilterPort6Index OBJECT-TYPE 
		SYNTAX Unsigned32 
		MAX-ACCESS not-accessible 
		STATUS current 
		DESCRIPTION 
		"Index for the table." 
		DEFVAL { 1 } 
		::= { indexFilterPort6Entry 1 }
        
    filterPort6 OBJECT-TYPE 
		SYNTAX Unsigned32
		MAX-ACCESS read-write
		STATUS current 
		DESCRIPTION 
		"A maximum 4 byte filter that shall be matched.
         Less than 4 bytes can be matched if the mask is set up for that." 
		DEFVAL { 1 } 
		::= { indexFilterPort6Entry 2 }
        
    validEgressPort6 OBJECT-TYPE 
		SYNTAX  TruthValue
		MAX-ACCESS read-write
		STATUS current 
		DESCRIPTION 
		"True if this filter is valid on egress." 
		DEFVAL { 2 } 
		::= { indexFilterPort6Entry 3 }

    validIngressPort6 OBJECT-TYPE 
		SYNTAX  TruthValue
		MAX-ACCESS read-write
		STATUS current 
		DESCRIPTION 
		"True if this filter is valid on ingress." 
		DEFVAL { 2 } 
		::= { indexFilterPort6Entry 4 }
        
    filterStatusPort6 OBJECT-TYPE 
		SYNTAX RowStatus
		MAX-ACCESS read-create
		STATUS current 
		DESCRIPTION 
		"Only createAndGo(4) is allowed when creating a new filter." 
		DEFVAL { 4 } 
		::= { indexFilterPort6Entry 5 }          
     

--  
-- Index filters for switch port 7
--
	indexFilterPort7Table OBJECT-TYPE 
		SYNTAX SEQUENCE OF IndexFilterPort7Entry 
		MAX-ACCESS not-accessible 
		STATUS current 
		DESCRIPTION 
			"Index filters for switch port 7.
            
            Note: This will only work if the index filtering feature is enabled."
	::= { indexFilter 7 }
			
	indexFilterPort7Entry OBJECT-TYPE 
		SYNTAX IndexFilterPort7Entry 
		MAX-ACCESS not-accessible 
		STATUS current 
		DESCRIPTION 
			"Entry in the index port filter table." 
		INDEX { indexFilterPort7Index } 
	::= { indexFilterPort7Table 1 } 
	
	IndexFilterPort7Entry ::= SEQUENCE { 
		indexFilterPort7Index 
		Unsigned32, 
		filterPort7 
		Unsigned32,
        validEgressPort7
        TruthValue,
		validIngressPort7
        TruthValue,
		filterStatusPort7
		RowStatus		
	}
	  
	indexFilterPort7Index OBJECT-TYPE 
		SYNTAX Unsigned32 
		MAX-ACCESS not-accessible 
		STATUS current 
		DESCRIPTION 
		"Index for the table." 
		DEFVAL { 1 } 
		::= { indexFilterPort7Entry 1 }
        
    filterPort7 OBJECT-TYPE 
		SYNTAX Unsigned32
		MAX-ACCESS read-write
		STATUS current 
		DESCRIPTION 
		"A maximum 4 byte filter that shall be matched.
         Less than 4 bytes can be matched if the mask is set up for that." 
		DEFVAL { 1 } 
		::= { indexFilterPort7Entry 2 }
        
    validEgressPort7 OBJECT-TYPE 
		SYNTAX  TruthValue
		MAX-ACCESS read-write
		STATUS current 
		DESCRIPTION 
		"True if this filter is valid on egress." 
		DEFVAL { 2 } 
		::= { indexFilterPort7Entry 3 }

    validIngressPort7 OBJECT-TYPE 
		SYNTAX  TruthValue
		MAX-ACCESS read-write
		STATUS current 
		DESCRIPTION 
		"True if this filter is valid on ingress." 
		DEFVAL { 2 } 
		::= { indexFilterPort7Entry 4 }
        
    filterStatusPort7 OBJECT-TYPE 
		SYNTAX RowStatus
		MAX-ACCESS read-create
		STATUS current 
		DESCRIPTION 
		"Only createAndGo(4) is allowed when creating a new filter." 
		DEFVAL { 4 } 
		::= { indexFilterPort7Entry 5 }  


--  
-- Index filters for switch port 8
--
	indexFilterPort8Table OBJECT-TYPE 
		SYNTAX SEQUENCE OF IndexFilterPort8Entry 
		MAX-ACCESS not-accessible 
		STATUS current 
		DESCRIPTION 
			"Index filters for switch port 8.
            
            Note: This will only work if the index filtering feature is enabled."
	::= { indexFilter 8 }
			
	indexFilterPort8Entry OBJECT-TYPE 
		SYNTAX IndexFilterPort8Entry 
		MAX-ACCESS not-accessible 
		STATUS current 
		DESCRIPTION 
			"Entry in the index port filter table." 
		INDEX { indexFilterPort8Index } 
	::= { indexFilterPort8Table 1 } 
	
	IndexFilterPort8Entry ::= SEQUENCE { 
		indexFilterPort8Index 
		Unsigned32, 
		filterPort8 
		Unsigned32,
        validEgressPort8
        TruthValue,
		validIngressPort8
        TruthValue,
		filterStatusPort8
		RowStatus		
	}
	  
	indexFilterPort8Index OBJECT-TYPE 
		SYNTAX Unsigned32 
		MAX-ACCESS not-accessible 
		STATUS current 
		DESCRIPTION 
		"Index for the table." 
		DEFVAL { 1 } 
		::= { indexFilterPort8Entry 1 }
        
    filterPort8 OBJECT-TYPE 
		SYNTAX Unsigned32
		MAX-ACCESS read-write
		STATUS current 
		DESCRIPTION 
		"A maximum 4 byte filter that shall be matched.
         Less than 4 bytes can be matched if the mask is set up for that." 
		DEFVAL { 1 } 
		::= { indexFilterPort8Entry 2 }
        
    validEgressPort8 OBJECT-TYPE 
		SYNTAX  TruthValue
		MAX-ACCESS read-write
		STATUS current 
		DESCRIPTION 
		"True if this filter is valid on egress." 
		DEFVAL { 2 } 
		::= { indexFilterPort8Entry 3 }

    validIngressPort8 OBJECT-TYPE 
		SYNTAX  TruthValue
		MAX-ACCESS read-write
		STATUS current 
		DESCRIPTION 
		"True if this filter is valid on ingress." 
		DEFVAL { 2 } 
		::= { indexFilterPort8Entry 4 }
        
    filterStatusPort8 OBJECT-TYPE 
		SYNTAX RowStatus
		MAX-ACCESS read-create
		STATUS current 
		DESCRIPTION 
		"Only createAndGo(4) is allowed when creating a new filter." 
		DEFVAL { 4 } 
		::= { indexFilterPort8Entry 5 }  
        
--  
-- Index filter configuration
--
	indexFilterConfigTable OBJECT-TYPE 
		SYNTAX SEQUENCE OF IndexFilterConfigEntry 
		MAX-ACCESS not-accessible 
		STATUS current 
		DESCRIPTION 
			"Index filter configuration.
            
            Note: This will only work if the index filtering feature is enabled."
	::= { indexFilter 9 }
			
	indexFilterConfigEntry OBJECT-TYPE 
		SYNTAX IndexFilterConfigEntry 
		MAX-ACCESS not-accessible 
		STATUS current 
		DESCRIPTION 
			"Entry in the index filtering config table." 
		INDEX { indexFilterConfigIndex } 
	::= { indexFilterConfigTable 1 } 
	
	IndexFilterConfigEntry ::= SEQUENCE { 
		indexFilterConfigIndex 
		Unsigned32, 
		enableEgressFilter
		TruthValue,
        egressMode
        INTEGER,
        filterType
        INTEGER,
        filterIndex
        Unsigned32,
        filterMask
        Unsigned32
	}
	  
	indexFilterConfigIndex OBJECT-TYPE 
		SYNTAX Unsigned32 
		MAX-ACCESS not-accessible 
		STATUS current 
		DESCRIPTION 
		"Index for the table." 
		DEFVAL { 1 } 
		::= { indexFilterConfigEntry 1 }
        
    enableEgressFilter OBJECT-TYPE 
		SYNTAX  TruthValue
		MAX-ACCESS read-write
		STATUS current 
		DESCRIPTION 
		"True if filters shall be matched on egress." 
		DEFVAL { 2 } 
		::= { indexFilterConfigEntry 2 }
        
    egressMode OBJECT-TYPE 
	SYNTAX  INTEGER {
            pass (1),   
            block (2)
        }
		MAX-ACCESS read-write
		STATUS current 
		DESCRIPTION 
		"Block: Block packet when match.
         Pass: Pass packet when match." 
		DEFVAL { 2 } 
		::= { indexFilterConfigEntry 3 }
               
    filterType OBJECT-TYPE 
	SYNTAX  INTEGER {   
            specifyFilterIndex (1),
            udpDestPort (2),
            udpSourcePort (3),
            udpSourceAndDestPort (4),
            ipSourcePort (5),
            ipDestPort (6)
        }
		MAX-ACCESS read-write
		STATUS current 
		DESCRIPTION 
		"1: Specify the index in the Ethernet packet (starting at 0) to 
            filter on. The filter index and mask must be specified.
            
         2: Filter on UDP destination port.
            The filter index and mask is automatically set and cannot be altered.
            
         3: Filter on UDP source port.
            The filter index and mask is automatically set and cannot be altered.
            
         4: Filter on UDP source and destination port.
            The filter index and mask is automatically set and cannot be altered.
            
         5: Filter on IP source port.
            The filter index and mask is automatically set and cannot be altered.
            
         6: Filter on IP destination port.
            The filter index and mask is automatically set and cannot be altered." 
		DEFVAL { 1 } 
		::= { indexFilterConfigEntry 4 }               
        
    filterIndex OBJECT-TYPE 
	SYNTAX  Unsigned32 (0..4294967295)
		MAX-ACCESS read-write
		STATUS current 
		DESCRIPTION 
		"Starting byte number in the packet that should be matched
         with the filter.
         Byte 0 is the most significant byte of the source MAC address." 
		DEFVAL { 0 } 
		::= { indexFilterConfigEntry 5 } 
               
    filterMask OBJECT-TYPE 
	SYNTAX  Unsigned32 (0..4294967295)
		MAX-ACCESS read-write
		STATUS current 
		DESCRIPTION 
		"Mask of the filter that must match" 
		DEFVAL { 0 } 
		::= { indexFilterConfigEntry 6 }
		
--  
-- NTP functionality
--

    ntpClientEnable OBJECT-TYPE
		SYNTAX  TruthValue
        MAX-ACCESS read-write
        STATUS current
        DESCRIPTION
        "Enable or disable the NTP client"
		::= { ntp 1 }
		
	ntpClientQueryInterval OBJECT-TYPE 
	SYNTAX  Integer32
		MAX-ACCESS read-write
		STATUS current 
		DESCRIPTION 
		"This is the minimum interval between transmitted messages, in seconds
		 as a power of two. For instance, a value of six indicates a minimum
		 interval of 64 seconds. " 
		DEFVAL { 0 } 
		::= { ntp 2 }
		
	ntpServerIpAddress OBJECT-TYPE
	    SYNTAX     IpAddress
        MAX-ACCESS read-write
        STATUS current
        DESCRIPTION
        "IPv4 address of the NTP server."
		::= { ntp 3 }
		
	ntpClientOffset OBJECT-TYPE 
	SYNTAX  Integer32
		MAX-ACCESS read-only
		STATUS current 
		DESCRIPTION 
		"Current NTP client offset from server in us." 		
		::= { ntp 4 }
		
END
